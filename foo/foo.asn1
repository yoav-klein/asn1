FooProtocol DEFINITIONS ::= BEGIN

    FooQuestion ::= SEQUENCE {
        
        trackingNumber INTEGER,
        question       IA5String
    }

    FooAnswer ::= SEQUENCE {
        questionNumber INTEGER,
        answer         BOOLEAN
    }

END
